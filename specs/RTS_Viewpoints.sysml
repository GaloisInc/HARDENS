import Views::*;

package 'RTS Viewpoints and Views' {
  import 'RTS Stakeholders';
  
  viewpoint 'NRC Customer Viewpoint' {
    
  }
  
  view def 'NRC Customer View Definition' {
    
  }
  
  view 'NRC Customer View Definition' {
    
  }
  
  viewpoint 'Galois Performer Viewpoint' {
    
  }
  
  view def 'Galois Performer View Definition' {
    
  }
  
  view 'Galois PI View' : 'Galois Performer View Definition' {
  
  }
  
  view 'Galois PL View' : 'Galois Performer View Definition' {
  
  }

  view 'Galois Software Engineer View' : 'Galois Performer View Definition' {
    
  }
  
  view 'Galois Hardware Engineer View' : 'Galois Performer View Definition' {
    
  } 
}
