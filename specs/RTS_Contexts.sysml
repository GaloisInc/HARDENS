package 'RTS System Contexts' {
  import 'RTS Architecture'::*;
  import 'Kiniry RTS System Architecture Draft'::*;
  
  // Definitions of system contexts
  // part def RTS_System_Context :> Base_RTS_System_Context;
  
  // Definitions of relevant connections
}
